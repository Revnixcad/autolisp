; Developer
; Nico Bos
(vl-load-com)
; Add path of this repository to Support File Search Path in AutoCAD
(load "scripts/nbo-calculation.lsp")

;@@@@@@@@@@@@@@@@@@@@@@@@@@@@@@@@@@@@@@@@@@@@@@@@@@@@@ 
; MAIN PROGRAM 
;@@@@@@@@@@@@@@@@@@@@@@@@@@@@@@@@@@@@@@@@@@@@@@@@@@@@@
