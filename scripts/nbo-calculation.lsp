(defun c:NBO-CALC-TOTAL-LENGHT (/ $distance $entity $number $point1 $point2 $selection) 
  (if (ssget '((0 . "LINE,POLYLINE,LWPOLYLINE,ARC,CIRCLE,ELLIPSE,SPLINE,MLINE,REGION,MPOLYGON")))
    (progn
      (setq $distance 0)
      (vlax-for $entity (setq $selection (vla-get-activeselectionset (vla-get-activedocument (vlax-get-acad-object))))
	(cond
	  ((member (vla-get-objectname $entity) '("AcDbLine" "AcDb3dPolyline" "AcDbPolyline"))
	    (setq $distance (+ $distance (vla-get-length $entity)))
	  )
	  ((eq (vla-get-objectname $entity) "AcDbArc")
	    (setq $distance (+ $distance (vla-get-arclength $entity)))
	  )
	  ((eq (vla-get-objectname $entity) "AcDbCircle")
	    (setq $distance (+ $distance (vla-get-circumference $entity)))
	  )
	  ((member (vla-get-objectname $entity) '("AcDbSpline" "AcDbEllipse"))
	    (setq $distance (+ $distance (vlax-curve-getdistatparam $entity (vlax-curve-getendparam $entity))))
	  )
	  ((eq (vla-get-objectname $entity) "AcDbMline")
	    (setq $number 0 $point2 nil)
	    (while (nth $number (setq lst (vlax-get $entity 'Coordinates)))
	      (setq $point1 (list (nth $number lst)(nth (1+ $number) lst)(nth (+ $number 2) lst)))
	      (and $point2
		(setq $distance (+ $distance (distance $point1 $point2)))
	      )
	      (setq $point2 $point1
		    $number (+ $number 3)
	      )
	    )
	  )
	  ((member (vla-get-objectname $entity) '("AcDbMPolygon" "AcDbRegion"))
	    (setq $distance (+ $distance (vla-get-perimeter $entity)))
	  )
	)
      )
      (if (eq (vla-get-count $selection) 1)
          (princ (strcat "\nThe Total Length of the Object is : " (rtos $distance)))
          (princ (strcat "\nThe Total Length of the " (itoa (vla-get-count $selection)) " Objects are : " (rtos $distance)))
      )
      (vla-delete $selection)
    )
  )
  (princ)
)
